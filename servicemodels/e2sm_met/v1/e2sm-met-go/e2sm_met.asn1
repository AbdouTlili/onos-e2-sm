-- ASN1START
-- **************************************************************
-- E2SM-MET 2.0.1 Information Element Definitions
-- **************************************************************

E2SM-MET-IEs {
    iso(1) identified-organization(3) dod(6) internet(1) private(4) enterprise(1) oran(53148) e2(1) version2(2) e2sm(2) e2sm-METMON-IEs (97)}
    DEFINITIONS AUTOMATIC TAGS ::= 
    
    BEGIN
    
    TimeStamp ::= OCTET STRING (SIZE(4))
    
    -- **************************************************************
    
    CellObjectID ::= INTEGER (0.. 255, ...)
    
    GranularityPeriod ::= INTEGER (1.. 4294967295)
    
    SubscriptionID ::= INTEGER (1.. 4294967296, ...)
    
    -- **************************************************************
    
    GlobalMETnode-ID ::= INTEGER (1.. 4294967296, ...)
    
    -- **************************************************************
    
    RANfunction-Name ::= SEQUENCE{
        ranFunction-ShortName		PrintableString(SIZE(1..150,...)),
        ranFunction-E2SM-OID		PrintableString(SIZE(1..1000,...)),
        ranFunction-Description		PrintableString(SIZE(1..150,...)),
        ...
    }
    
    -- **************************************************************
    --   Lists
    -- **************************************************************
    
    maxnoofMeasurementInfo		INTEGER ::= 65536
    maxnoofMeasurementRecord	INTEGER ::= 65536
    maxnoofMeasurementValue		INTEGER ::= 65536

    -- ****************** 
    -- UE related defs 
    maxofUE             		INTEGER ::= 65536

    UEID ::= INTEGER (1.. 4294967296, ...)

    UETag ::= PrintableString(SIZE(1.. 150, ...))

    UEItem ::= SEQUENCE {
        ueID	UEID,
        ueTag   UETag   OPTIONAL,
        ...
    }

    --****************
    
    MeasurementInfoList ::= SEQUENCE (SIZE(1..maxnoofMeasurementInfo)) OF MeasurementInfoItem
    
    MeasurementInfoItem ::= SEQUENCE {
        measType				PrintableString (SIZE (0..15), ...),
        ...
    }
    
    MeasurementData ::= SEQUENCE (SIZE(1..maxnoofMeasurementRecord)) OF MeasurementRecord
    
    MeasurementRecord ::= SEQUENCE {
        ueID					UEID,
        ueTag                   UETag,
        measRecordItem  SEQUENCE (SIZE(1..maxnoofMeasurementValue)) OF MeasurementRecordItem,
        ...
    }
    
    MeasurementRecordItem ::= CHOICE {
        integer					INTEGER,
        real					REAL,
        noValue					NULL,
        ...
    }
    
    -- **************************************************************
    -- E2SM-MET Service Model IEs
    -- **************************************************************
    
    -- **************************************************************
    --   Event Trigger Definition OCTET STRING contents
    -- **************************************************************
    
    E2SM-MET-EventTriggerDefinition ::= SEQUENCE{
        eventDefinition-formats			CHOICE{
            eventDefinition-Format1			E2SM-MET-EventTriggerDefinition-Format1,
            ...
        },
        ...
    }
    
    E2SM-MET-EventTriggerDefinition-Format1 ::= SEQUENCE{
        reportingPeriod					INTEGER,
        ...
    }
    
    -- **************************************************************
    --   Action Definition OCTET STRING contents
    -- **************************************************************
    
    -- **************************************************************
    --   Indication Header OCTET STRING contents
    -- **************************************************************
    
    E2SM-MET-IndicationHeader ::= SEQUENCE{
        indicationHeader-formats		CHOICE{
            indicationHeader-Format1		E2SM-MET-IndicationHeader-Format1,
            ...
        },
        ...
    }
    
    E2SM-MET-IndicationHeader-Format1 ::= SEQUENCE{
        colletStartTime					TimeStamp,
        fileFormatversion				PrintableString (SIZE (0..15), ...)		OPTIONAL,
        senderName						PrintableString (SIZE (0..400), ...)	OPTIONAL,
        metNodeID						GlobalMETnode-ID						OPTIONAL,
        ...
    }
    
    -- **************************************************************
    --   Indication Message OCTET STRING contents
    -- **************************************************************
    
    E2SM-MET-IndicationMessage ::= SEQUENCE{
        indicationMessage-formats		CHOICE{
            indicationMessage-Format1		E2SM-MET-IndicationMessage-Format1,
            ...
        },
        ...
    }
    
    E2SM-MET-IndicationMessage-Format1 ::= SEQUENCE {
        subscriptID						SubscriptionID,
        cellObjID						CellObjectID							OPTIONAL,
        granulPeriod					GranularityPeriod 						OPTIONAL,
        measInfoList					MeasurementInfoList						OPTIONAL,
        measData						MeasurementData,
        ...
    }
    
    -- ***************************************************************
    --   RAN Function Definition OCTET STRING contents
    -- ***************************************************************
    
    E2SM-MET-RANfunction-Description ::= SEQUENCE{
        ranFunction-Name				RANfunction-Name,
        ...
    }
    
    END

    -- ASN1STOP
